QTS-MIB DEFINITIONS ::= BEGIN

   IMPORTS
      enterprises, TimeTicks
         FROM SNMPv2-SMI
      OBJECT-GROUP, MODULE-COMPLIANCE
                FROM SNMPv2-CONF
      Integer32, IpAddress, Counter64, OBJECT-TYPE, NOTIFICATION-TYPE, MODULE-IDENTITY
         FROM SNMPv2-SMI;

qnap MODULE-IDENTITY
     LAST-UPDATED "202002200000Z"
     ORGANIZATION "www.qnap.com"
     CONTACT-INFO
          "support@qnap.com"
     DESCRIPTION
         "NAS mib"
     REVISION     "202002200000Z"
     DESCRIPTION
         "NAS mib ver 2.0"
     ::= { enterprises 55062 }

    qutshero OBJECT IDENTIFIER ::= { qnap 2 }

 -- Frame Relay Multiplexer MIB groups

-- Storage
    storage             OBJECT IDENTIFIER ::= { qutshero 10 }

diskCount OBJECT-TYPE
    SYNTAX  Integer32
    MAX-ACCESS  read-only
    STATUS  current
    DESCRIPTION
            "The number of hard drive."
    ::= { storage 1 }
diskTable OBJECT-TYPE
    SYNTAX  SEQUENCE OF DiskTableEntryDef
    MAX-ACCESS  not-accessible
    STATUS  current
    DESCRIPTION
            "A list of hard drive entries.  The number of
            entries is given by the value of diskCount."
    ::= { storage 2 }
diskTableEntry OBJECT-TYPE
    SYNTAX  DiskTableEntryDef
    MAX-ACCESS  not-accessible
    STATUS  current
    DESCRIPTION
            "An disk entry containing objects at the disk."
    INDEX   { diskIndex }
    ::= { diskTable 1 }

DiskTableEntryDef ::=
    SEQUENCE {
        diskIndex Integer32 ,
        diskID Integer32 ,
        diskManufacturer OCTET STRING,
        diskModel OCTET STRING,
        diskSerialNumber OCTET STRING,
        diskType OCTET STRING,
        diskStatus OCTET STRING,
        diskTemperature Integer32,
        diskCapacity Counter64
    }
diskIndex OBJECT-TYPE
    SYNTAX  Integer32  (1..4094)
    MAX-ACCESS  not-accessible
    STATUS  current
    DESCRIPTION
            "A unique value for each hard drive. Its value
            ranges between 1 and the value of diskCount.  The
            value for each hard drive must remain constant at
            least from one re-initialization of the entity's
             management system to the next re-initialization."
    ::= { diskTableEntry 1 }

diskID OBJECT-TYPE
    SYNTAX  Integer32
    MAX-ACCESS  read-only
    STATUS  current
    DESCRIPTION
            "A unique value for each hard drive."
    ::= { diskTableEntry 2 }

diskManufacturer OBJECT-TYPE
    SYNTAX  OCTET STRING (SIZE (0..255))
    MAX-ACCESS  read-only
    STATUS  current
    DESCRIPTION
            "The manufacturer of hard drive."
    ::= { diskTableEntry 3 }

diskModel OBJECT-TYPE
    SYNTAX  OCTET STRING
    MAX-ACCESS  read-only
    STATUS  current
    DESCRIPTION
            "Hard disk Model"
    ::= { diskTableEntry 4 }

diskSerialNumber OBJECT-TYPE
    SYNTAX  OCTET STRING
    MAX-ACCESS  read-only
    STATUS  current
    DESCRIPTION
            "The serialNumber of hard drive."
    ::= { diskTableEntry 5 }

diskType OBJECT-TYPE
    SYNTAX  OCTET STRING
    MAX-ACCESS  read-only
    STATUS  current
    DESCRIPTION "The type of hard drive."
    ::= { diskTableEntry 6}

diskStatus OBJECT-TYPE
    SYNTAX  OCTET STRING
    MAX-ACCESS  read-only
    STATUS  current
    DESCRIPTION "The status of hard drive."
    ::= { diskTableEntry 7 }

diskTemperature OBJECT-TYPE
    SYNTAX  Integer32
    MAX-ACCESS  read-only
    STATUS  current
    DESCRIPTION "The temperature of hard drive."
    ::= { diskTableEntry 8 }

diskCapacity OBJECT-TYPE
    SYNTAX  Counter64
    MAX-ACCESS  read-only
    STATUS  current
    DESCRIPTION "The capacity in byte of hard drive."
    ::= { diskTableEntry 9 }


--raid table
raidCount OBJECT-TYPE
    SYNTAX  Integer32
    MAX-ACCESS  read-only
    STATUS  current
    DESCRIPTION
            "The number of RAID."
    ::= { storage 4 }

raidTable OBJECT-TYPE
    SYNTAX  SEQUENCE OF RaidTableEntryDef
    MAX-ACCESS  not-accessible
    STATUS  current
    DESCRIPTION
            "A list of RAID entries.  The number of
            entries is given by the value of raidCount."
    ::= { storage 5 }

raidTableEntry OBJECT-TYPE
    SYNTAX  RaidTableEntryDef
    MAX-ACCESS  not-accessible
    STATUS  current
    DESCRIPTION
            "RAID table"
    INDEX   { raidIndex }
    ::= { raidTable 1 }

RaidTableEntryDef ::=
    SEQUENCE {
        raidIndex Integer32 ,
        raidID Integer32 ,
        raidName OCTET STRING,
        raidStatus OCTET STRING,
        raidCapacity Counter64,
        raidBitmap Integer32 ,
        raidLevel OCTET STRING
    }
raidIndex OBJECT-TYPE
    SYNTAX  Integer32 (0..4096)
    MAX-ACCESS  not-accessible
    STATUS  current
    DESCRIPTION
            "A unique value for each  RAID. Its value
            ranges between 1 and the value of raidCount.  The
            value for each RAID must remain constant at
            least from one re-initialization of the entity's
            RAID to the next re-initialization."
    ::= { raidTableEntry 1 }

raidID OBJECT-TYPE
    SYNTAX  Integer32
    MAX-ACCESS  read-only
    STATUS  current
    DESCRIPTION
            "A unique value for each RAID."
    ::= { raidTableEntry 2 }

raidName OBJECT-TYPE
    SYNTAX  OCTET STRING (SIZE (0..255))
    MAX-ACCESS  read-only
    STATUS  current
    DESCRIPTION
            "The name of RAID"
    ::= { raidTableEntry 3 }

raidStatus OBJECT-TYPE
    SYNTAX  OCTET STRING (SIZE (0..255))
    MAX-ACCESS  read-only
    STATUS  current
    DESCRIPTION
            "The status of RAID"
    ::= { raidTableEntry 4 }

raidCapacity OBJECT-TYPE
    SYNTAX  Counter64
    MAX-ACCESS  read-only
    STATUS  current
    DESCRIPTION "The total capacity in byte of RAID."
    ::= { raidTableEntry 5 }

raidBitmap OBJECT-TYPE
    SYNTAX  Integer32
    MAX-ACCESS  read-only
    STATUS  current
    DESCRIPTION
            "RAID bit map"
    ::= { raidTableEntry 6 }

raidLevel OBJECT-TYPE
    SYNTAX  OCTET STRING (SIZE (0..255))
    MAX-ACCESS  read-only
    STATUS  current
    DESCRIPTION
            "RAID level"
    ::= { raidTableEntry 7 }

-- pool
storagepoolCount OBJECT-TYPE
    SYNTAX  Integer32
    MAX-ACCESS  read-only
    STATUS  current
    DESCRIPTION
            "The number of pool."
    ::= { storage 6 }

storagepoolTable OBJECT-TYPE
    SYNTAX  SEQUENCE OF StoragepoolTableEntryDef
    MAX-ACCESS  not-accessible
    STATUS  current
    DESCRIPTION
            "A list of storage pool entries.  The number of
            entries is given by the value of storagepoolCount."
    ::= { storage 7 }

storagepoolTableEntry OBJECT-TYPE
    SYNTAX  StoragepoolTableEntryDef
    MAX-ACCESS  not-accessible
    STATUS  current
    DESCRIPTION
            "Pool table"
    INDEX   { storagepoolIndex }
    ::= { storagepoolTable 1 }

StoragepoolTableEntryDef ::=
    SEQUENCE {
        storagepoolIndex Integer32 ,
        storagepoolID Integer32 ,
        storagepoolCapacity Counter64,
        storagepoolFreeSize Counter64,
        storagepoolStatus Integer32
    }
storagepoolIndex OBJECT-TYPE
    SYNTAX  Integer32 (0..4096)
    MAX-ACCESS  not-accessible
    STATUS  current
    DESCRIPTION
            "A unique value for each  storage pool. Its value
            ranges between 1 and the value of storagepoolCount.  The
            value for each interface must remain constant at
            least from one re-initialization of the entity's
            Pool to the next re-initialization."
    ::= { storagepoolTableEntry 1 }

storagepoolID OBJECT-TYPE
    SYNTAX  Integer32
    MAX-ACCESS  read-only
    STATUS  current
    DESCRIPTION
            "Pool ID"
    ::= { storagepoolTableEntry 2 }

storagepoolCapacity OBJECT-TYPE
    SYNTAX  Counter64
    MAX-ACCESS  read-only
    STATUS  current
    DESCRIPTION "Pool capacity in byte."
    ::= { storagepoolTableEntry 3 }

storagepoolFreeSize OBJECT-TYPE
    SYNTAX  Counter64
    MAX-ACCESS  read-only
    STATUS  current
    DESCRIPTION "Pool free size in byte."
    ::= { storagepoolTableEntry 4 }

storagepoolStatus OBJECT-TYPE
    SYNTAX  INTEGER  {
            error(-3),
            notReady(-2),
            warning(-1),
            ready(0)
    }
    MAX-ACCESS  read-only
    STATUS  current
    DESCRIPTION
            "
    ** QuTS version
    SED_LOCKED       = -6,
    DETACHING        = -5,
    REMOVING         = -4,
    ERROR            = -3,
    NOT_READY        = -2,
    WARNING          = -1,
    READY            =  0,
    ENABLE_QTIER     =  1,
    SED_LOCKING      =  2,
    SED_UNLOCKING    =  3,
    KS-Redmine#39712.
    REMOVING_TIER    =  4,
    NONE_STATUS      =  0xFF,

    ** for QuHERO version
    SED_LOCKED      = -4,
    ERROR           = -3,
    NOT_READY       = -2,
    WARNING         = -1,
    READY           = 0,
    RESILVERING     = 1,
    EXPORTING       = 2,
    REMOVING        = 3,
    SCRUBBING       = 4,
    CREATING        = 5,
    SED_LOCKING     = 6,
    SED_UNLOCKING   = 7,
    STOPPING        = 8,
    STOPPED         = 9,
    STARTING        = 10,
    IMPORTING       = 11,
    READONLY        = 12,
    PRUNING         = 13,
    TUNING          = 14,
    NONE_STATUS     = 0xFF,"
    ::= { storagepoolTableEntry 5}

sharedFolderCount OBJECT-TYPE
    SYNTAX  Integer32
    MAX-ACCESS  read-only
    STATUS  current
    DESCRIPTION
            "The number of system shared folders (regardless of
            their current state) present on this system."
    ::= { storage 8 }

sharedFolderTable OBJECT-TYPE
    SYNTAX  SEQUENCE OF SharedFolderTableEntryDef
    MAX-ACCESS  not-accessible
    STATUS  current
    DESCRIPTION
            "A list of shared Folder entries.  The number of
            entries is given by the value of SysVolumeNumber."
    ::= { storage 9 }

sharedFolderTableEntry OBJECT-TYPE
    SYNTAX  SharedFolderTableEntryDef
    MAX-ACCESS  not-accessible
    STATUS  current
    DESCRIPTION
            "An system shared Folder entry"
    INDEX   { sharedFolderIndex }
    ::= { sharedFolderTable 1 }

SharedFolderTableEntryDef ::=
    SEQUENCE {
        sharedFolderIndex                Integer32,
        sharedFolderName                 OCTET STRING,
        sharedFolderCapacity             Counter64,
        sharedFolderFreeSize             Counter64,
        sharedFolderStatus               OCTET STRING,
        sharedFolderBlockSize            OCTET STRING,
        sharedFolderWORMStatus           INTEGER,
        sharedFolderCompressionEnabled   INTEGER,
        sharedFolderDeduplicationEnabled INTEGER,
        sharedFolderSpaceAllocation      OCTET STRING,
        sharedFolderEncryptionEnabled    INTEGER,
        sharedFolderssdCacheEnabled      INTEGER,
        sharedFolderSyncIOType           INTEGER
    }
sharedFolderIndex OBJECT-TYPE
    SYNTAX  INTEGER (0..4096)
    MAX-ACCESS  not-accessible
    STATUS  current
    DESCRIPTION
            "A unique value for each shared folder. Its value
            ranges between 1 and the value of volumeCount.  The
            value for each shared folder must remain constant at
            least from one re-initialization of the entity's
            shared folder system to the next re-initialization."
    ::= { sharedFolderTableEntry 1 }


sharedFolderName OBJECT-TYPE
    SYNTAX  OCTET STRING (SIZE (0..255))
    MAX-ACCESS  read-only
    STATUS  current
    DESCRIPTION "Shared folder Name."
    ::= { sharedFolderTableEntry 2 }

sharedFolderCapacity OBJECT-TYPE
    SYNTAX  Counter64
    MAX-ACCESS  read-only
    STATUS  current
    DESCRIPTION "Shared folder total size in byte."
    ::= { sharedFolderTableEntry 3 }

sharedFolderFreeSize OBJECT-TYPE
    SYNTAX  Counter64
    MAX-ACCESS  read-only
    STATUS  current
    DESCRIPTION "Shared folder free size in byte."
    ::= { sharedFolderTableEntry 4 }

sharedFolderStatus OBJECT-TYPE
    SYNTAX  OCTET STRING (SIZE (0..255))
    MAX-ACCESS  read-only
    STATUS  current
    DESCRIPTION "Volume status"
    ::= { sharedFolderTableEntry 5 }

sharedFolderBlockSize OBJECT-TYPE
    SYNTAX  OCTET STRING
    MAX-ACCESS  read-only
    STATUS  current
    DESCRIPTION "Block size of shared folder."
    ::= { sharedFolderTableEntry 6 }

sharedFolderWORMStatus OBJECT-TYPE
    SYNTAX  INTEGER{
                   no(0),
                   enterprise(1),
                   compliance(2)
                   }
    MAX-ACCESS  read-only
    STATUS  current
    DESCRIPTION "WORM status."
    ::= { sharedFolderTableEntry 7 }

sharedFolderCompressionEnabled OBJECT-TYPE
    SYNTAX  INTEGER{
                   no(0),
                   yes(1)
                   }
    MAX-ACCESS  read-only
    STATUS  current
    DESCRIPTION "Compression enabled or not."
    ::= { sharedFolderTableEntry 8 }

sharedFolderDeduplicationEnabled OBJECT-TYPE
    SYNTAX  INTEGER{
                   no(0),
                   yes(1)
                   }
    MAX-ACCESS  read-only
    STATUS  current
    DESCRIPTION "Deduplication enabled or not."
    ::= { sharedFolderTableEntry 9 }

sharedFolderSpaceAllocation OBJECT-TYPE
    SYNTAX  OCTET STRING
    MAX-ACCESS  read-only
    STATUS  current
    DESCRIPTION "Space allocation of shared folder."
    ::= { sharedFolderTableEntry 10 }

sharedFolderEncryptionEnabled OBJECT-TYPE
    SYNTAX  INTEGER{
                   no(0),
                   yes(1)
                   }
    MAX-ACCESS  read-only
    STATUS  current
    DESCRIPTION "Encryption enabled or not."
    ::= { sharedFolderTableEntry 11 }

sharedFolderssdCacheEnabled OBJECT-TYPE
    SYNTAX  INTEGER{
                   no(0),
                   yes(1)
                   }
    MAX-ACCESS  read-only
    STATUS  current
    DESCRIPTION "Cache enabled or not."
    ::= { sharedFolderTableEntry 12 }

sharedFolderSyncIOType OBJECT-TYPE
    SYNTAX  INTEGER{
                   standard(0),
                   always(1),
                   none(2)
                   }
    MAX-ACCESS  read-only
    STATUS  current
    DESCRIPTION "Sync IO type of shared folder."
    ::= { sharedFolderTableEntry 13 }

--cache
cacheAccelerationServiceEnabled OBJECT-TYPE
    SYNTAX  INTEGER {
                   no(0),
                   yes(1)
                   }
    MAX-ACCESS  read-only
    STATUS  current
    DESCRIPTION
            "If acceleration service of cache is enabled."
    ::= { storage 10 }

cacheAvailablePercent OBJECT-TYPE
    SYNTAX  Integer32
    MAX-ACCESS  read-only
    STATUS  current
    DESCRIPTION
            "Available percent of cache."
    ::= { storage 11 }

cacheReadHitRate OBJECT-TYPE
    SYNTAX  Integer32
    MAX-ACCESS  read-only
    STATUS  current
    DESCRIPTION
            "Read hit rate percent of cache."
    ::= { storage 12 }

cacheWriteHitRate OBJECT-TYPE
    SYNTAX  Integer32
    MAX-ACCESS  read-only
    STATUS  current
    DESCRIPTION
            "Write hit rate percent of cache."
    ::= { storage 13 }

cacheStatus OBJECT-TYPE
    SYNTAX  Integer32
    MAX-ACCESS  read-only
    STATUS  current
    DESCRIPTION
            "Status of cache."
    ::= { storage 14 }

cacheType OBJECT-TYPE
    SYNTAX  INTEGER
    {
        readOnly (0),
        readWrite (1),
        writeOnly (2)
    }
    MAX-ACCESS  read-only
    STATUS  current
    DESCRIPTION
            "Cache Type. 0: Read-Only, 1: Read-Write, 2: Write-Only"
    ::= { storage 15 }

cacheRAIDType OBJECT-TYPE
    SYNTAX  OCTET STRING
    MAX-ACCESS  read-only
    STATUS  current
    DESCRIPTION
            "RAID Type : Single, RAID 0, RAID 1, RAID 5, etc"
    ::= { storage 16 }

cacheMode OBJECT-TYPE
    SYNTAX  OCTET STRING
    MAX-ACCESS  read-only
    STATUS  current
    DESCRIPTION
            "Random I/O, All I/O"
    ::= { storage 17 }

iSCSIServiceEnabled OBJECT-TYPE
    SYNTAX  INTEGER {
                   no(0),
                   yes(1)
                   }
    MAX-ACCESS  read-only
    STATUS  current
    DESCRIPTION "iSCSI Service enable or not."
    ::= { storage 18 }

iSCSIServicePort OBJECT-TYPE
    SYNTAX  Integer32
    MAX-ACCESS  read-only
    STATUS  current
    DESCRIPTION "iSCSI Service Port."
    ::= { storage 23 }

iSNSService OBJECT-TYPE
    SYNTAX  INTEGER {
                   no(0),
                   yes(1)
                   }
    MAX-ACCESS  read-only
    STATUS  current
    DESCRIPTION "iSNS Service."
    ::= { storage 24 }

iSNSIP OBJECT-TYPE
    SYNTAX  IpAddress
    MAX-ACCESS  read-only
    STATUS  current
    DESCRIPTION "iSNS IP."
    ::= { storage 25 }

lunCount OBJECT-TYPE
    SYNTAX  Integer32
    MAX-ACCESS  read-only
    STATUS  current
    DESCRIPTION
            "The number of LUNs (regardless of
            their current state) present on this system."
    ::= { storage 19 }

lunTable OBJECT-TYPE
    SYNTAX  SEQUENCE OF LUNTableEntryDef
    MAX-ACCESS  not-accessible
    STATUS  current
    DESCRIPTION
            "LUN table"
    ::= { storage 20 }

lunTableEntry OBJECT-TYPE
    SYNTAX  LUNTableEntryDef
    MAX-ACCESS  not-accessible
    STATUS  current
    DESCRIPTION
            "An LUN entry."
    INDEX   { lunIndex }
    ::= { lunTable 1 }

LUNTableEntryDef ::=
    SEQUENCE {
        lunIndex Integer32 ,
        lunID Integer32 ,
        lunCapacity Counter64,
        lunUsedPercent Integer32 ,
        lunStatus OCTET STRING,
        lunName OCTET STRING,
        lunBackupStatus INTEGER ,
        lunIsMap INTEGER
    }
lunIndex OBJECT-TYPE
    SYNTAX  Integer32 (0..4096)
    MAX-ACCESS  not-accessible
    STATUS  current
    DESCRIPTION "LUN Index."
    ::= { lunTableEntry 1 }

lunID OBJECT-TYPE
    SYNTAX  Integer32
    MAX-ACCESS  read-only
    STATUS  current
    DESCRIPTION "LUN ID."
    ::= { lunTableEntry 2 }

lunCapacity OBJECT-TYPE
    SYNTAX  Counter64
    MAX-ACCESS  read-only
    STATUS  current
    DESCRIPTION "LUN capacity in byte."
    ::= { lunTableEntry 3 }

lunUsedPercent OBJECT-TYPE
    SYNTAX  Integer32
    MAX-ACCESS  read-only
    STATUS  current
    DESCRIPTION "LUN used percent."
    ::= { lunTableEntry 4 }

lunStatus OBJECT-TYPE
    SYNTAX  OCTET STRING (SIZE (0..255))
    MAX-ACCESS  read-only
    STATUS  current
    DESCRIPTION "LUN status."
    ::= { lunTableEntry 5 }

lunName OBJECT-TYPE
    SYNTAX  OCTET STRING (SIZE (0..255))
    MAX-ACCESS  read-only
    STATUS  current
    DESCRIPTION "LUN name."
    ::= { lunTableEntry 6 }

lunBackupStatus OBJECT-TYPE
    SYNTAX  INTEGER {
                   none(0),
                   backup(1),
                   restore(2),
                   snapshot(3)
                   }
    MAX-ACCESS  read-only
    STATUS  current
    DESCRIPTION "LUN backup status."
    ::= { lunTableEntry 7 }

lunIsMap OBJECT-TYPE
    SYNTAX  INTEGER {
                   unmapped(0),
                   mapped(1)
                   }
    MAX-ACCESS  read-only
    STATUS  current
    DESCRIPTION "LUN is Mapped or not."
    ::= { lunTableEntry 8 }

targetCount OBJECT-TYPE
    SYNTAX  Integer32
    MAX-ACCESS  read-only
    STATUS  current
    DESCRIPTION
            "The number of Targets (regardless of
            their current state) present on this system."
    ::= { storage 21 }

targeTable OBJECT-TYPE
    SYNTAX  SEQUENCE OF TargeTableEntryDef
    MAX-ACCESS  not-accessible
    STATUS  current
    DESCRIPTION
            "A list of Target entries.  The number of
            entries is given by the value of TargetNumber."
    ::= { storage 22 }

targeTableEntry OBJECT-TYPE
    SYNTAX  TargeTableEntryDef
    MAX-ACCESS  not-accessible
    STATUS  current
    DESCRIPTION
            "A target entry."
    INDEX   { targetIndex }
    ::= { targeTable 1 }

TargeTableEntryDef ::=
    SEQUENCE {
        targetIndex Integer32 ,
        targetID Integer32 ,
        targetName OCTET STRING,
        targetIQN OCTET STRING,
        targetServerIP OCTET STRING,
        targetStatus INTEGER
    }

targetIndex OBJECT-TYPE
    SYNTAX  Integer32 (0..4096)
    MAX-ACCESS  not-accessible
    STATUS  current
    DESCRIPTION "TargetIndex."
    ::= { targeTableEntry 1 }

targetID OBJECT-TYPE
    SYNTAX  Integer32
    MAX-ACCESS  read-only
    STATUS  current
    DESCRIPTION "Target ID."
    ::= { targeTableEntry 2 }

targetName OBJECT-TYPE
    SYNTAX  OCTET STRING (SIZE (0..255))
    MAX-ACCESS  read-only
    STATUS  current
    DESCRIPTION "Target name."
    ::= { targeTableEntry 3 }

targetIQN OBJECT-TYPE
    SYNTAX  OCTET STRING (SIZE (0..255))
    MAX-ACCESS  read-only
    STATUS  current
    DESCRIPTION "TargetIQN."
    ::= { targeTableEntry 4 }

targetServerIP OBJECT-TYPE
    SYNTAX  OCTET STRING (SIZE (0..255))
    MAX-ACCESS  read-only
    STATUS  current
    DESCRIPTION "Target Server IP Address."
    ::= { targeTableEntry 5 }

targetStatus OBJECT-TYPE
    SYNTAX  INTEGER {
                   offline(-1),
                   ready(0),
                   connected(1)
                   }
    MAX-ACCESS  read-only
    STATUS  current
    DESCRIPTION "Target status."
    ::= { targeTableEntry 6 }

--FC
fiberChannelPortsCount OBJECT-TYPE
    SYNTAX  Integer32
    MAX-ACCESS  read-only
    STATUS  current
    DESCRIPTION
            "The number of Targets (regardless of their current state) present on this system."
    ::= { storage 27 }

fcPortsTable OBJECT-TYPE
    SYNTAX  SEQUENCE OF FCPortsTableEntryDef
    MAX-ACCESS  not-accessible
    STATUS  current
    DESCRIPTION
            "A list of msatadisks.  The number of
            entries is given by the value of msataDiskNumber."
    ::= { storage 28 }
fcPortsTableEntry OBJECT-TYPE
    SYNTAX  FCPortsTableEntryDef
    MAX-ACCESS  not-accessible
    STATUS  current
    DESCRIPTION
            "A fc ports entry."
    INDEX   { fcPortIndex }
    ::= { fcPortsTable 1 }
FCPortsTableEntryDef ::=
    SEQUENCE {
        fcPortIndex Integer32 ,
        fcAdapter OCTET STRING,
        fcAdapterManufacturer OCTET STRING,
        fcStatus OCTET STRING,
        fcAdapterSpeed OCTET STRING,
        fcPortWWPN OCTET STRING,
        fcPortAlias OCTET STRING,
        fcPortInitiators Integer32
    }
fcPortIndex OBJECT-TYPE
    SYNTAX  Integer32 (0..4096)
    MAX-ACCESS  not-accessible
    STATUS  current
    DESCRIPTION "fcPortIndex."
    ::= { fcPortsTableEntry 1 }

fcAdapter OBJECT-TYPE
    SYNTAX  OCTET STRING
    MAX-ACCESS  read-only
    STATUS  current
    DESCRIPTION "fcAdapter."
    ::= { fcPortsTableEntry 2 }

fcAdapterManufacturer OBJECT-TYPE
    SYNTAX  OCTET STRING
    MAX-ACCESS  read-only
    STATUS  current
    DESCRIPTION "fcAdapterManufacturer."
    ::= { fcPortsTableEntry 3 }

fcStatus OBJECT-TYPE
    SYNTAX  OCTET STRING
    MAX-ACCESS  read-only
    STATUS  current
    DESCRIPTION "fcStatus."
    ::= { fcPortsTableEntry 4 }

fcAdapterSpeed OBJECT-TYPE
    SYNTAX  OCTET STRING
    MAX-ACCESS  read-only
    STATUS  current
    DESCRIPTION "fcAdapterSpeed."
    ::= { fcPortsTableEntry 5 }

fcPortWWPN OBJECT-TYPE
    SYNTAX  OCTET STRING
    MAX-ACCESS  read-only
    STATUS  current
    DESCRIPTION "fcPortWWPN."
    ::= { fcPortsTableEntry 6 }

fcPortAlias OBJECT-TYPE
    SYNTAX  OCTET STRING
    MAX-ACCESS  read-only
    STATUS  current
    DESCRIPTION "fcPortAlias."
    ::= { fcPortsTableEntry 7 }

fcPortInitiators OBJECT-TYPE
    SYNTAX  Integer32
    MAX-ACCESS  read-only
    STATUS  current
    DESCRIPTION "fcPortInitiators."
    ::= { fcPortsTableEntry 8 }

fcPortGroupCount OBJECT-TYPE
    SYNTAX  Integer32
    MAX-ACCESS  read-only
    STATUS  current
    DESCRIPTION
            "The number of Targets (regardless of their current state) present on this system."
    ::= { storage 29 }

fcPortGroupTable OBJECT-TYPE
    SYNTAX  SEQUENCE OF FCPortsGroupTableEntryDef
    MAX-ACCESS  not-accessible
    STATUS  current
    DESCRIPTION
            "A list of msatadisks.  The number of
            entries is given by the value of msataDiskNumber."
    ::= { storage 30  }
fcPortGroupTableEntry OBJECT-TYPE
    SYNTAX  FCPortsGroupTableEntryDef
    MAX-ACCESS  not-accessible
    STATUS  current
    DESCRIPTION
            "A fc ports entry."
    INDEX   { fcPortIndex }
    ::= { fcPortGroupTable 1 }
FCPortsGroupTableEntryDef ::=
    SEQUENCE {
        fcPortGrouptIndex Integer32,
        fcPortGroupName OCTET STRING,
        fcPortGroupType OCTET STRING,
        fcPortGroupStorageCapacity Counter64,
        fcPortGroupStorageAllocation Counter64,
        fcPortGroupStatus OCTET STRING
    }
fcPortGrouptIndex OBJECT-TYPE
    SYNTAX  Integer32 (0..4096)
    MAX-ACCESS  not-accessible
    STATUS  current
    DESCRIPTION "fcPortGrouptIndex."
    ::= { fcPortGroupTableEntry 1 }

fcPortGroupName OBJECT-TYPE
    SYNTAX  OCTET STRING
    MAX-ACCESS  read-only
    STATUS  current
    DESCRIPTION "fcPortGroupName."
    ::= { fcPortGroupTableEntry 2 }

fcPortGroupType OBJECT-TYPE
    SYNTAX  OCTET STRING
    MAX-ACCESS  read-only
    STATUS  current
    DESCRIPTION "fcPortGroupType."
    ::= { fcPortGroupTableEntry 3 }

fcPortGroupStorageCapacity OBJECT-TYPE
    SYNTAX  Counter64
    MAX-ACCESS  read-only
    STATUS  current
    DESCRIPTION "fcPortGroupStorageCapacity."
    ::= { fcPortGroupTableEntry 4 }

fcPortGroupStorageAllocation OBJECT-TYPE
    SYNTAX  Counter64
    MAX-ACCESS  read-only
    STATUS  current
    DESCRIPTION "fcPortGroupStorageAllocation."
    ::= { fcPortGroupTableEntry 5 }

fcPortGroupStatus OBJECT-TYPE
    SYNTAX  OCTET STRING
    MAX-ACCESS  read-only
    STATUS  current
    DESCRIPTION "fcPortGroupStatus."
    ::= { fcPortGroupTableEntry 6 }

-- msataDiskTable
msataDiskCount OBJECT-TYPE
    SYNTAX  Integer32
    MAX-ACCESS  read-only
    STATUS  current
    DESCRIPTION
            "The number of msatadisks (regardless of
            their current state) present on this system."
    ::= { storage 31 }

msataDiskTable OBJECT-TYPE
    SYNTAX  SEQUENCE OF MsataDiskTableEntryDef
    MAX-ACCESS  not-accessible
    STATUS  current
    DESCRIPTION
            "A list of msatadisks.  The number of
            entries is given by the value of msataDiskNumber."
    ::= { storage 32 }

msataDiskTableEntry OBJECT-TYPE
    SYNTAX  MsataDiskTableEntryDef
    MAX-ACCESS  not-accessible
    STATUS  current
    DESCRIPTION
            "A disk entry."
    INDEX   { msataDiskIndex }
    ::= { msataDiskTable 1 }

MsataDiskTableEntryDef ::=
    SEQUENCE {
        msataDiskIndex Integer32 ,
        msataDiskID Integer32 ,
        msataDiskEnclosureID Integer32 ,
        msataDiskSummary OCTET STRING,
        msataDiskSmartInfo INTEGER ,
        msataDiskTemperture Integer32 ,
        msataDiskGlobalSpare INTEGER ,
        msataDiskModel OCTET STRING,
        msataDiskCapacity Counter64
    }
msataDiskIndex OBJECT-TYPE
    SYNTAX  Integer32 (0..4096)
    MAX-ACCESS  not-accessible
    STATUS  current
    DESCRIPTION "DiskIndex."
    ::= { msataDiskTableEntry 1 }

msataDiskID OBJECT-TYPE
    SYNTAX  Integer32
    MAX-ACCESS  read-only
    STATUS  current
    DESCRIPTION "mSATA DiskID."
    ::= { msataDiskTableEntry 2 }

msataDiskEnclosureID OBJECT-TYPE
    SYNTAX  Integer32
    MAX-ACCESS  read-only
    STATUS  current
    DESCRIPTION "mSATA disk EnclosureID."
    ::= { msataDiskTableEntry 3 }

msataDiskSummary OBJECT-TYPE
    SYNTAX  OCTET STRING  (SIZE (0..255))
    MAX-ACCESS  read-only
    STATUS  current
    DESCRIPTION "mSATA Disk status summary. 'Good',''Warning','Abnormal'"
    ::= { msataDiskTableEntry 4 }

msataDiskSmartInfo OBJECT-TYPE
    SYNTAX  INTEGER {
                    error(-1),
                    good(0),
                    warning(1),
                    abnormal(2)
                   }
    MAX-ACCESS  read-only
    STATUS  current
    DESCRIPTION "mSATA Disk smart information."
    ::= { msataDiskTableEntry 5 }

msataDiskTemperture OBJECT-TYPE
    SYNTAX  Integer32
    MAX-ACCESS  read-only
    STATUS  current
    DESCRIPTION "mSATA Disk temperture."
    ::= { msataDiskTableEntry 6 }

msataDiskGlobalSpare OBJECT-TYPE
    SYNTAX  INTEGER {
                   no(0),
                   yes(1)
                   }
    MAX-ACCESS  read-only
    STATUS  current
    DESCRIPTION "mSATA Disk global spare."
    ::= { msataDiskTableEntry 7 }

msataDiskModel OBJECT-TYPE
    SYNTAX  OCTET STRING  (SIZE (0..255))
    MAX-ACCESS  read-only
    STATUS  current
    DESCRIPTION "mSATA Disk model."
    ::= { msataDiskTableEntry 8 }

msataDiskCapacity OBJECT-TYPE
    SYNTAX  Counter64
    MAX-ACCESS  read-only
    STATUS  current
    DESCRIPTION "mSATA Disk Capacity in bytes."
    ::= { msataDiskTableEntry 9 }

enclosurelCount OBJECT-TYPE
    SYNTAX  Integer32
    MAX-ACCESS  read-only
    STATUS  current
    DESCRIPTION
            "The number of Enclosures (regardless of
            their current state) present on this system."
    ::= { storage 33 }

enclosureTable OBJECT-TYPE
    SYNTAX  SEQUENCE OF EnclosureTableEntryDef
    MAX-ACCESS  not-accessible
    STATUS  current
    DESCRIPTION
            "A list of enclosures.  The number of
            entries is given by the value of EnclosureNumber."
    ::= { storage 34 }
enclosureTableEntry OBJECT-TYPE
    SYNTAX  EnclosureTableEntryDef
    MAX-ACCESS  not-accessible
    STATUS  current
    DESCRIPTION
            "An enclosure entry."
    INDEX   { enclosureIndex }
    ::= { enclosureTable 1 }
EnclosureTableEntryDef ::=
    SEQUENCE {
        enclosureIndex Integer32 ,
        enclosureID Integer32 ,
        enclosureModel OCTET STRING,
        enclosureSerialNum OCTET STRING,
        enclosureSlot Integer32 ,
        enclosureName OCTET STRING,
        enclosureSystemTemp Integer32
    }

enclosureIndex OBJECT-TYPE
    SYNTAX  Integer32 (0..4096)
    MAX-ACCESS  not-accessible
    STATUS  current
    DESCRIPTION "EnclosureIndex."
    ::= { enclosureTableEntry 1 }

enclosureID OBJECT-TYPE
    SYNTAX  Integer32
    MAX-ACCESS  read-only
    STATUS  current
    DESCRIPTION "enclosureID."
    ::= { enclosureTableEntry 2 }

enclosureModel OBJECT-TYPE
    SYNTAX  OCTET STRING  (SIZE (0..255))
    MAX-ACCESS  read-only
    STATUS  current
    DESCRIPTION "EnclosureModel."
    ::= { enclosureTableEntry 3 }

enclosureSerialNum OBJECT-TYPE
    SYNTAX  OCTET STRING  (SIZE (0..255))
    MAX-ACCESS  read-only
    STATUS  current
    DESCRIPTION "EnclosureSerialNum."
    ::= { enclosureTableEntry 4 }

enclosureSlot OBJECT-TYPE
    SYNTAX  Integer32
    MAX-ACCESS  read-only
    STATUS  current
    DESCRIPTION "EnclosureSlot."
    ::= { enclosureTableEntry 5 }

enclosureName OBJECT-TYPE
    SYNTAX  OCTET STRING
    MAX-ACCESS  read-only
    STATUS  current
    DESCRIPTION "Enclosure Name."
    ::= { enclosureTableEntry 6 }

enclosureSystemTemp OBJECT-TYPE
    SYNTAX  Integer32
    MAX-ACCESS  read-only
    STATUS  current
    DESCRIPTION "Enclosure System temperature in centigrade."
    ::= { enclosureTableEntry 7 }



-- diskSMARTInfoTable

diskSMARTInfoTable OBJECT-TYPE
    SYNTAX  SEQUENCE OF DiskSMARTInfoTableEntryDef
    MAX-ACCESS  not-accessible
    STATUS  current
    DESCRIPTION
            "Disk smart information table."
    ::= { storage 3 }
diskSMARTInfoTableEntry OBJECT-TYPE
    SYNTAX  DiskSMARTInfoTableEntryDef
    MAX-ACCESS  not-accessible
    STATUS  current
    DESCRIPTION
            "A smartinfo entry."
    INDEX   { diskSMARTInfoIndex }
    ::= { diskSMARTInfoTable 1 }
DiskSMARTInfoTableEntryDef ::=
    SEQUENCE {
        diskSMARTInfoIndex Integer32 ,
        diskSMARTInfoDeviceName OCTET STRING,
        diskSMARTInfoAttributeName OCTET STRING,
        diskSMARTInfoAttributeID Integer32 ,
        diskSMARTInfoAttributeCurrent Integer32 ,
        diskSMARTInfoAttributeWorst Integer32 ,
        diskSMARTInfoAttributeThreshold Integer32 ,
        diskSMARTInfoAttributeRAW Counter64 ,
        diskSMARTInfoAttributeStatus OCTET STRING
    }
diskSMARTInfoIndex OBJECT-TYPE
    SYNTAX  Integer32 (0..2147483647)
    MAX-ACCESS  not-accessible
    STATUS  current
    DESCRIPTION "diskSMARTInfoIndex."
    ::= { diskSMARTInfoTableEntry 1 }

diskSMARTInfoDeviceName OBJECT-TYPE
    SYNTAX  OCTET STRING
    MAX-ACCESS  read-only
    STATUS  current
    DESCRIPTION "diskSMARTInfoDeviceName."
    ::= { diskSMARTInfoTableEntry 2 }

diskSMARTInfoAttributeName OBJECT-TYPE
    SYNTAX  OCTET STRING
    MAX-ACCESS  read-only
    STATUS  current
    DESCRIPTION "diskSMARTInfoAttributeName."
    ::= { diskSMARTInfoTableEntry 3 }

diskSMARTInfoAttributeID OBJECT-TYPE
    SYNTAX  Integer32
    MAX-ACCESS  read-only
    STATUS  current
    DESCRIPTION "diskSMARTInfoAttributeID."
    ::= { diskSMARTInfoTableEntry 4 }

diskSMARTInfoAttributeCurrent OBJECT-TYPE
    SYNTAX  Integer32
    MAX-ACCESS  read-only
    STATUS  current
    DESCRIPTION "diskSMARTInfoAttributeCurrent."
    ::= { diskSMARTInfoTableEntry 5 }

diskSMARTInfoAttributeWorst OBJECT-TYPE
    SYNTAX  Integer32
    MAX-ACCESS  read-only
    STATUS  current
    DESCRIPTION "diskSMARTInfoAttributeCurrent."
    ::= { diskSMARTInfoTableEntry 6 }

diskSMARTInfoAttributeThreshold OBJECT-TYPE
    SYNTAX  Integer32
    MAX-ACCESS  read-only
    STATUS  current
    DESCRIPTION "diskSMARTInfoAttributeCurrent."
    ::= { diskSMARTInfoTableEntry 7}

diskSMARTInfoAttributeRAW OBJECT-TYPE
    SYNTAX  Counter64
    MAX-ACCESS  read-only
    STATUS  current
    DESCRIPTION "diskSMARTInfoAttributeCurrent."
    ::= { diskSMARTInfoTableEntry 8}

diskSMARTInfoAttributeStatus OBJECT-TYPE
    SYNTAX  OCTET STRING
    MAX-ACCESS  read-only
    STATUS  current
    DESCRIPTION "diskSMARTInfoAttributeCurrent."
    ::= { diskSMARTInfoTableEntry 9}

-- JBOD
 jBODInfo OBJECT IDENTIFIER ::= { storage 26 }

 jBODBitmap OBJECT-TYPE
     SYNTAX  OCTET STRING
     MAX-ACCESS  read-only
     STATUS  current
     DESCRIPTION
             "The bitmap  of JBOD (regardless of
             their current state) present on this system."
     ::= { jBODInfo 1 }


 jBODInfos OBJECT-TYPE
     SYNTAX  SEQUENCE OF JBODInfosEntryDef
     MAX-ACCESS  not-accessible
     STATUS  current
     DESCRIPTION
             "JBOD information."
     ::= { jBODInfo 2 }
 jBODInfosEntry OBJECT-TYPE
     SYNTAX  JBODInfosEntryDef
     MAX-ACCESS  not-accessible
     STATUS  current
     DESCRIPTION
             "JBOD infomation entry"
     INDEX   { jBODid }
     ::= { jBODInfos 1 }

 JBODInfosEntryDef ::=
     SEQUENCE {
         jBODid  Integer32 ,
         jBODHdNumber Integer32
         }

 jBODid OBJECT-TYPE
     SYNTAX  Integer32  (0..128)
     MAX-ACCESS  read-only
     STATUS  current
     DESCRIPTION
             "JBOD ID"
     ::= { jBODInfosEntry 1 }

 jBODHdNumber OBJECT-TYPE
     SYNTAX  Integer32
     MAX-ACCESS  read-only
     STATUS  current
     DESCRIPTION
             "JBOD port."
     ::= { jBODInfosEntry 2 }

 jBODHdTable1 OBJECT-TYPE
     SYNTAX  SEQUENCE OF JBODHdEntry1Def
     MAX-ACCESS  not-accessible
     STATUS  current
     DESCRIPTION
             "JBOD table"
     ::= { jBODInfo 3 }
 jBODHdEntry1 OBJECT-TYPE
     SYNTAX  JBODHdEntry1Def
     MAX-ACCESS  not-accessible
     STATUS  current
     DESCRIPTION
             "JBOD entry"
     INDEX   { jBODHdIndex1 }
     ::= { jBODHdTable1 1 }
 JBODHdEntry1Def ::=
     SEQUENCE {
         jBODHdIndex1  Integer32 ,
         jBODHdDescr1 OCTET STRING,
         jBODHdTemperature1 OCTET STRING,
         jBODHdStatus1 INTEGER ,
         jBODHdModel1 OCTET STRING,
         jBODHdCapacity1 OCTET STRING,
         jBODHdSmartInfo1 OCTET STRING
         }
 jBODHdIndex1 OBJECT-TYPE
     SYNTAX  Integer32 (0..512)
     MAX-ACCESS  not-accessible
     STATUS  current
     DESCRIPTION
             "JBOD table index"
     ::= { jBODHdEntry1 1 }
 jBODHdDescr1 OBJECT-TYPE
     SYNTAX  OCTET STRING (SIZE (0..255))
     MAX-ACCESS  read-only
     STATUS  current
     DESCRIPTION
             "JBOD description"
     ::= { jBODHdEntry1 2 }
 jBODHdTemperature1 OBJECT-TYPE
     SYNTAX  OCTET STRING
     MAX-ACCESS  read-only
     STATUS  current
     DESCRIPTION
             "JBOD disk temperature."
     ::= { jBODHdEntry1 3 }
 jBODHdStatus1 OBJECT-TYPE
     SYNTAX     INTEGER  {
         rwError(-9),
         invalid(-6),
         noDisk(-5),
         unknown(-4),
         ready(0)
         }
     MAX-ACCESS  read-only
     STATUS  current
     DESCRIPTION
             "JBOD disk status"
     ::= { jBODHdEntry1 4 }

 jBODHdModel1 OBJECT-TYPE
     SYNTAX  OCTET STRING
     MAX-ACCESS  read-only
     STATUS  current
     DESCRIPTION "JBOD disk model"
     ::= { jBODHdEntry1 5 }

 jBODHdCapacity1 OBJECT-TYPE
     SYNTAX  OCTET STRING
     MAX-ACCESS  read-only
     STATUS  current
     DESCRIPTION "JBOD disk capacity."
     ::= { jBODHdEntry1 6 }
 jBODHdSmartInfo1 OBJECT-TYPE
     SYNTAX  OCTET STRING
     MAX-ACCESS  read-only
     STATUS  current
     DESCRIPTION "JBOD disk SMART information."
     ::= { jBODHdEntry1 7 }

 jBODHdTable2 OBJECT-TYPE
     SYNTAX  SEQUENCE OF JBODHdEntry2Def
     MAX-ACCESS  not-accessible
     STATUS  current
     DESCRIPTION
             "JBOD table"
     ::= { jBODInfo 4}
 jBODHdEntry2 OBJECT-TYPE
     SYNTAX  JBODHdEntry2Def
     MAX-ACCESS  not-accessible
     STATUS  current
     DESCRIPTION
             "JBOD entry"
     INDEX   { jBODHdIndex2 }
     ::= { jBODHdTable2 1 }
 JBODHdEntry2Def ::=
     SEQUENCE {
         jBODHdIndex2  Integer32 ,
         jBODHdDescr2  OCTET STRING,
         jBODHdTemperature2  OCTET STRING,
         jBODHdStatus2  INTEGER ,
         jBODHdModel2  OCTET STRING,
         jBODHdCapacity2  OCTET STRING,
         jBODHdSmartInfo2  OCTET STRING
         }
 jBODHdIndex2  OBJECT-TYPE
     SYNTAX  Integer32 (0..512)
     MAX-ACCESS  not-accessible
     STATUS  current
     DESCRIPTION
             "JBOD table index"
     ::= { jBODHdEntry2  1 }
 jBODHdDescr2  OBJECT-TYPE
     SYNTAX  OCTET STRING (SIZE (0..255))
     MAX-ACCESS  read-only
     STATUS  current
     DESCRIPTION
             "JBOD disk description."
     ::= { jBODHdEntry2  2 }
 jBODHdTemperature2  OBJECT-TYPE
     SYNTAX  OCTET STRING
     MAX-ACCESS  read-only
     STATUS  current
     DESCRIPTION
             "JBOD disk temperature."
     ::= { jBODHdEntry2  3 }
 jBODHdStatus2  OBJECT-TYPE
     SYNTAX     INTEGER  {
         rwError(-9),
         invalid(-6),
         noDisk(-5),
         unknown(-4),
         ready(0)
         }
     MAX-ACCESS  read-only
     STATUS  current
     DESCRIPTION
             "JBOD disk status"
     ::= { jBODHdEntry2  4 }
 jBODHdModel2  OBJECT-TYPE
     SYNTAX  OCTET STRING
     MAX-ACCESS  read-only
     STATUS  current
     DESCRIPTION "JBOD disk model."
     ::= { jBODHdEntry2  5 }
 jBODHdCapacity2  OBJECT-TYPE
     SYNTAX  OCTET STRING
     MAX-ACCESS  read-only
     STATUS  current
     DESCRIPTION "JBOD disk capacity."
     ::= { jBODHdEntry2  6 }
 jBODHdSmartInfo2  OBJECT-TYPE
     SYNTAX  OCTET STRING
     MAX-ACCESS  read-only
     STATUS  current
     DESCRIPTION "JBOD disk SMART information."
     ::= { jBODHdEntry2  7 }

 jBODHdTable3 OBJECT-TYPE
     SYNTAX  SEQUENCE OF JBODHdEntry3Def
     MAX-ACCESS  not-accessible
     STATUS  current
     DESCRIPTION
             "JBOD table"
     ::= { jBODInfo 5 }

 jBODHdEntry3 OBJECT-TYPE
     SYNTAX  JBODHdEntry3Def
     MAX-ACCESS  not-accessible
     STATUS  current
     DESCRIPTION
             "JBOD entry"
     INDEX   { jBODHdIndex3 }
     ::= { jBODHdTable3 1 }
 JBODHdEntry3Def ::=
     SEQUENCE {
         jBODHdIndex3  Integer32 ,
         jBODHdDescr3 OCTET STRING,
         jBODHdTemperature3 OCTET STRING,
         jBODHdStatus3 INTEGER ,
         jBODHdModel3 OCTET STRING,
         jBODHdCapacity3 OCTET STRING,
         jBODHdSmartInfo3 OCTET STRING
         }
 jBODHdIndex3 OBJECT-TYPE
     SYNTAX  Integer32 (0..512)
     MAX-ACCESS  not-accessible
     STATUS  current
     DESCRIPTION
             "JBOD table index"
     ::= { jBODHdEntry3 1 }
 jBODHdDescr3 OBJECT-TYPE
     SYNTAX  OCTET STRING (SIZE (0..255))
     MAX-ACCESS  read-only
     STATUS  current
     DESCRIPTION
             "JBOD disk description"
     ::= { jBODHdEntry3 2 }
 jBODHdTemperature3 OBJECT-TYPE
     SYNTAX  OCTET STRING
     MAX-ACCESS  read-only
     STATUS  current
     DESCRIPTION
             "JBOD disk temperature."
     ::= { jBODHdEntry3 3 }
 jBODHdStatus3 OBJECT-TYPE
     SYNTAX     INTEGER  {
         rwError(-9),
         invalid(-6),
         noDisk(-5),
         unknown(-4),
         ready(0)
         }
     MAX-ACCESS  read-only
     STATUS  current
     DESCRIPTION
             "JBOD disk status."
     ::= { jBODHdEntry3 4 }
 jBODHdModel3 OBJECT-TYPE
     SYNTAX  OCTET STRING
     MAX-ACCESS  read-only
     STATUS  current
     DESCRIPTION "JBOD disk model."
     ::= { jBODHdEntry3 5 }
 jBODHdCapacity3 OBJECT-TYPE
     SYNTAX  OCTET STRING
     MAX-ACCESS  read-only
     STATUS  current
     DESCRIPTION "JBOD disk capacity."
     ::= { jBODHdEntry3 6 }
 jBODHdSmartInfo3 OBJECT-TYPE
     SYNTAX  OCTET STRING
     MAX-ACCESS  read-only
     STATUS  current
     DESCRIPTION "JBOD disk SMART information."
     ::= { jBODHdEntry3 7 }

 jBODHdTable4 OBJECT-TYPE
     SYNTAX  SEQUENCE OF JBODHdEntry4Def
     MAX-ACCESS  not-accessible
     STATUS  current
     DESCRIPTION
             "A list of interface entries.  The number of
             entries is given by the value of IfNumber."
     ::= { jBODInfo 6 }

 jBODHdEntry4 OBJECT-TYPE
     SYNTAX  JBODHdEntry4Def
     MAX-ACCESS  not-accessible
     STATUS  current
     DESCRIPTION
             "JBOD disk entry"
     INDEX   { jBODHdIndex4 }
     ::= { jBODHdTable4 1 }
 JBODHdEntry4Def ::=
     SEQUENCE {
         jBODHdIndex4  Integer32 ,
         jBODHdDescr4 OCTET STRING,
         jBODHdTemperature4 OCTET STRING,
         jBODHdStatus4 INTEGER ,
         jBODHdModel4 OCTET STRING,
         jBODHdCapacity4 OCTET STRING,
         jBODHdSmartInfo4 OCTET STRING
         }
 jBODHdIndex4 OBJECT-TYPE
     SYNTAX  Integer32 (0..512)
     MAX-ACCESS  not-accessible
     STATUS  current
     DESCRIPTION
             "JBOD table index"
     ::= { jBODHdEntry4 1 }
 jBODHdDescr4 OBJECT-TYPE
     SYNTAX  OCTET STRING (SIZE (0..255))
     MAX-ACCESS  read-only
     STATUS  current
     DESCRIPTION
             "JBOD disk description."
     ::= { jBODHdEntry4 2 }
 jBODHdTemperature4 OBJECT-TYPE
     SYNTAX  OCTET STRING
     MAX-ACCESS  read-only
     STATUS  current
     DESCRIPTION
             "JBOD disk temperature."
     ::= { jBODHdEntry4 3 }
 jBODHdStatus4 OBJECT-TYPE
     SYNTAX     INTEGER  {
         rwError(-9),
         invalid(-6),
         noDisk(-5),
         unknown(-4),
         ready(0)
         }
     MAX-ACCESS  read-only
     STATUS  current
     DESCRIPTION
             "JBOD disk status"
     ::= { jBODHdEntry4 4 }
 jBODHdModel4 OBJECT-TYPE
     SYNTAX  OCTET STRING
     MAX-ACCESS  read-only
     STATUS  current
     DESCRIPTION "JBOD disk model."
     ::= { jBODHdEntry4 5 }
 jBODHdCapacity4 OBJECT-TYPE
     SYNTAX  OCTET STRING
     MAX-ACCESS  read-only
     STATUS  current
     DESCRIPTION "JBOD disk capacity."
     ::= { jBODHdEntry4 6 }
 jBODHdSmartInfo4 OBJECT-TYPE
     SYNTAX  OCTET STRING
     MAX-ACCESS  read-only
     STATUS  current
     DESCRIPTION "JBOD disk SMART information."
     ::= { jBODHdEntry4 7 }

 jBODHdTable5 OBJECT-TYPE
     SYNTAX  SEQUENCE OF JBODHdEntry5Def
     MAX-ACCESS  not-accessible
     STATUS  current
     DESCRIPTION
             "JBOD table"
     ::= { jBODInfo 7 }

 jBODHdEntry5 OBJECT-TYPE
     SYNTAX  JBODHdEntry5Def
     MAX-ACCESS  not-accessible
     STATUS  current
     DESCRIPTION
             "JBOD disk entry"
     INDEX   { jBODHdIndex5 }
     ::= { jBODHdTable5 1 }
 JBODHdEntry5Def ::=
     SEQUENCE {
         jBODHdIndex5  Integer32 ,
         jBODHdDescr5 OCTET STRING,
         jBODHdTemperature5 OCTET STRING,
         jBODHdStatus5 INTEGER ,
         jBODHdModel5 OCTET STRING,
         jBODHdCapacity5 OCTET STRING,
         jBODHdSmartInfo5 OCTET STRING
         }
 jBODHdIndex5 OBJECT-TYPE
     SYNTAX  Integer32 (0..512)
     MAX-ACCESS  not-accessible
     STATUS  current
     DESCRIPTION
             "JBOD table index."
     ::= { jBODHdEntry5 1 }
 jBODHdDescr5 OBJECT-TYPE
     SYNTAX  OCTET STRING (SIZE (0..255))
     MAX-ACCESS  read-only
     STATUS  current
     DESCRIPTION
             "JBOD disk desription."
     ::= { jBODHdEntry5 2 }
 jBODHdTemperature5 OBJECT-TYPE
     SYNTAX  OCTET STRING
     MAX-ACCESS  read-only
     STATUS  current
     DESCRIPTION
             "Hard disk temperature."
     ::= { jBODHdEntry5 3 }
 jBODHdStatus5 OBJECT-TYPE
     SYNTAX     INTEGER  {
         rwError(-9),
         invalid(-6),
         noDisk(-5),
         unknown(-4),
         ready(0)
         }
     MAX-ACCESS  read-only
     STATUS  current
     DESCRIPTION
             "JBOD disk status."
     ::= { jBODHdEntry5 4 }
 jBODHdModel5 OBJECT-TYPE
     SYNTAX  OCTET STRING
     MAX-ACCESS  read-only
     STATUS  current
     DESCRIPTION "JBOD disk model."
     ::= { jBODHdEntry5 5 }
 jBODHdCapacity5 OBJECT-TYPE
     SYNTAX  OCTET STRING
     MAX-ACCESS  read-only
     STATUS  current
     DESCRIPTION "JBOD disk capacity."
     ::= { jBODHdEntry5 6 }
 jBODHdSmartInfo5 OBJECT-TYPE
     SYNTAX  OCTET STRING
     MAX-ACCESS  read-only
     STATUS  current
     DESCRIPTION "JBOD disk SMART information."
     ::= { jBODHdEntry5 7 }

 jBODHdTable6 OBJECT-TYPE
     SYNTAX  SEQUENCE OF JBODHdEntry6Def
     MAX-ACCESS  not-accessible
     STATUS  current
     DESCRIPTION
             "JBOD table"
     ::= { jBODInfo 8 }

 jBODHdEntry6 OBJECT-TYPE
     SYNTAX  JBODHdEntry6Def
     MAX-ACCESS  not-accessible
     STATUS  current
     DESCRIPTION
             "JBOD disk entry"
     INDEX   { jBODHdIndex6 }
     ::= { jBODHdTable6 1 }
 JBODHdEntry6Def ::=
     SEQUENCE {
         jBODHdIndex6  Integer32 ,
         jBODHdDescr6 OCTET STRING,
         jBODHdTemperature6 OCTET STRING,
         jBODHdStatus6 INTEGER ,
         jBODHdModel6 OCTET STRING,
         jBODHdCapacity6 OCTET STRING,
         jBODHdSmartInfo6 OCTET STRING
         }
 jBODHdIndex6 OBJECT-TYPE
     SYNTAX  Integer32 (0..512)
     MAX-ACCESS  not-accessible
     STATUS  current
     DESCRIPTION
             "JBOD table index"
     ::= { jBODHdEntry6 1 }
 jBODHdDescr6 OBJECT-TYPE
     SYNTAX  OCTET STRING (SIZE (0..255))
     MAX-ACCESS  read-only
     STATUS  current
     DESCRIPTION
             "JBOD disk description."
     ::= { jBODHdEntry6 2 }
 jBODHdTemperature6 OBJECT-TYPE
     SYNTAX  OCTET STRING
     MAX-ACCESS  read-only
     STATUS  current
     DESCRIPTION
             "JBOD disk temperature."
     ::= { jBODHdEntry6 3 }
 jBODHdStatus6 OBJECT-TYPE
     SYNTAX     INTEGER  {
         rwError(-9),
         invalid(-6),
         noDisk(-5),
         unknown(-4),
         ready(0)
         }
     MAX-ACCESS  read-only
     STATUS  current
     DESCRIPTION
             "JBOD status."
     ::= { jBODHdEntry6 4 }
 jBODHdModel6 OBJECT-TYPE
     SYNTAX  OCTET STRING
     MAX-ACCESS  read-only
     STATUS  current
     DESCRIPTION "JBOD disk model."
     ::= { jBODHdEntry6 5 }
 jBODHdCapacity6 OBJECT-TYPE
     SYNTAX  OCTET STRING
     MAX-ACCESS  read-only
     STATUS  current
     DESCRIPTION "JBOD disk capacity."
     ::= { jBODHdEntry6 6 }
 jBODHdSmartInfo6 OBJECT-TYPE
     SYNTAX  OCTET STRING
     MAX-ACCESS  read-only
     STATUS  current
     DESCRIPTION "JBOD disk SMART information."
     ::= { jBODHdEntry6 7 }

 jBODHdTable7 OBJECT-TYPE
     SYNTAX  SEQUENCE OF JBODHdEntry7Def
     MAX-ACCESS  not-accessible
     STATUS  current
     DESCRIPTION
             "JBOD table."
     ::= { jBODInfo 9 }

 jBODHdEntry7 OBJECT-TYPE
     SYNTAX  JBODHdEntry7Def
     MAX-ACCESS  not-accessible
     STATUS  current
     DESCRIPTION
             "JBOD disk entry"
     INDEX   { jBODHdIndex7 }
     ::= { jBODHdTable7 1 }
 JBODHdEntry7Def ::=
     SEQUENCE {
         jBODHdIndex7  Integer32 ,
         jBODHdDescr7 OCTET STRING,
         jBODHdTemperature7 OCTET STRING,
         jBODHdStatus7 INTEGER ,
         jBODHdModel7 OCTET STRING,
         jBODHdCapacity7 OCTET STRING,
         jBODHdSmartInfo7 OCTET STRING
         }
 jBODHdIndex7 OBJECT-TYPE
     SYNTAX  Integer32 (0..512)
     MAX-ACCESS  not-accessible
     STATUS  current
     DESCRIPTION
             "JBOD table index."
     ::= { jBODHdEntry7 1 }
 jBODHdDescr7 OBJECT-TYPE
     SYNTAX  OCTET STRING (SIZE (0..255))
     MAX-ACCESS  read-only
     STATUS  current
     DESCRIPTION
             "JBOD disk description."
     ::= { jBODHdEntry7 2 }
 jBODHdTemperature7 OBJECT-TYPE
     SYNTAX  OCTET STRING
     MAX-ACCESS  read-only
     STATUS  current
     DESCRIPTION
             "JBOD disk temperature."
     ::= { jBODHdEntry7 3 }
 jBODHdStatus7 OBJECT-TYPE
     SYNTAX     INTEGER  {
         rwError(-9),
         invalid(-6),
         noDisk(-5),
         unknown(-4),
         ready(0)
         }
     MAX-ACCESS  read-only
     STATUS  current
     DESCRIPTION
             "JBOD disk status."
     ::= { jBODHdEntry7 4 }
 jBODHdModel7 OBJECT-TYPE
     SYNTAX  OCTET STRING
     MAX-ACCESS  read-only
     STATUS  current
     DESCRIPTION "JBOD disk model."
     ::= { jBODHdEntry7 5 }
 jBODHdCapacity7 OBJECT-TYPE
     SYNTAX  OCTET STRING
     MAX-ACCESS  read-only
     STATUS  current
     DESCRIPTION "JBOD disk capacity."
     ::= { jBODHdEntry7 6 }
 jBODHdSmartInfo7 OBJECT-TYPE
     SYNTAX  OCTET STRING
     MAX-ACCESS  read-only
     STATUS  current
     DESCRIPTION "JBOD disk SMART information."
     ::= { jBODHdEntry7 7 }

 jBODHdTable8 OBJECT-TYPE
     SYNTAX  SEQUENCE OF JBODHdEntry8Def
     MAX-ACCESS  not-accessible
     STATUS  current
     DESCRIPTION
             "JBOD table."
     ::= { jBODInfo 10 }

 jBODHdEntry8 OBJECT-TYPE
     SYNTAX  JBODHdEntry8Def
     MAX-ACCESS  not-accessible
     STATUS  current
     DESCRIPTION
             "JBOD disk entry"
     INDEX   { jBODHdIndex8 }
     ::= { jBODHdTable8 1 }
 JBODHdEntry8Def ::=
     SEQUENCE {
         jBODHdIndex8  Integer32 ,
         jBODHdDescr8 OCTET STRING,
         jBODHdTemperature8 OCTET STRING,
         jBODHdStatus8 INTEGER ,
         jBODHdModel8 OCTET STRING,
         jBODHdCapacity8 OCTET STRING,
         jBODHdSmartInfo8 OCTET STRING
         }
 jBODHdIndex8 OBJECT-TYPE
     SYNTAX  Integer32 (0..512)
     MAX-ACCESS  not-accessible
     STATUS  current
     DESCRIPTION
             "JBOD table index."
     ::= { jBODHdEntry8 1 }
 jBODHdDescr8 OBJECT-TYPE
     SYNTAX  OCTET STRING (SIZE (0..255))
     MAX-ACCESS  read-only
     STATUS  current
     DESCRIPTION
             "JBOD disk description."
     ::= { jBODHdEntry8 2 }
 jBODHdTemperature8 OBJECT-TYPE
     SYNTAX  OCTET STRING
     MAX-ACCESS  read-only
     STATUS  current
     DESCRIPTION
             "JBOD disk temperature."
     ::= { jBODHdEntry8 3 }
 jBODHdStatus8 OBJECT-TYPE
     SYNTAX     INTEGER  {
         rwError(-9),
         invalid(-6),
         noDisk(-5),
         unknown(-4),
         ready(0)
         }
     MAX-ACCESS  read-only
     STATUS  current
     DESCRIPTION
             "JBOD disk status."
     ::= { jBODHdEntry8 4 }
 jBODHdModel8 OBJECT-TYPE
     SYNTAX  OCTET STRING
     MAX-ACCESS  read-only
     STATUS  current
     DESCRIPTION "JBOD disk model."
     ::= { jBODHdEntry8 5 }
 jBODHdCapacity8 OBJECT-TYPE
     SYNTAX  OCTET STRING
     MAX-ACCESS  read-only
     STATUS  current
     DESCRIPTION "JBOD disk capacity."
     ::= { jBODHdEntry8 6 }
 jBODHdSmartInfo8 OBJECT-TYPE
     SYNTAX  OCTET STRING
     MAX-ACCESS  read-only
     STATUS  current
     DESCRIPTION "JBOD disk SMART information."
     ::= { jBODHdEntry8 7 }
 -- system
    system            OBJECT IDENTIFIER ::= { qutshero 12 }

 -- system Event
systemEventMsg        OBJECT IDENTIFIER ::= { system 1 }

 -- system event
  eventInformMsg OBJECT-TYPE
       SYNTAX  OCTET STRING
       MAX-ACCESS  read-only
       STATUS  current
       DESCRIPTION
            "Information event of NAS system."
      ::= { systemEventMsg 101 }

  eventWarningMsg OBJECT-TYPE
      SYNTAX  OCTET STRING
      MAX-ACCESS  read-only
      STATUS  current
      DESCRIPTION
           "Warning event of NAS system."
      ::= { systemEventMsg 102 }

  eventErrorMsg OBJECT-TYPE
      SYNTAX  OCTET STRING
      MAX-ACCESS  read-only
      STATUS  current
      DESCRIPTION
           "Error event of NAS system."
      ::= { systemEventMsg 103 }

systemTraps OBJECT IDENTIFIER ::= { system  2 }

  eventInform NOTIFICATION-TYPE
      OBJECTS  { eventInformMsg }
      STATUS current
      DESCRIPTION
           "Info: %s"
      ::=  { systemTraps 1 }

  eventWarning NOTIFICATION-TYPE
      OBJECTS  { eventWarningMsg }
      STATUS current
      DESCRIPTION
          "Warn: %s"
      ::=  { systemTraps 2 }

  eventError NOTIFICATION-TYPE
      OBJECTS  { eventErrorMsg }
      STATUS current
      DESCRIPTION
           "Error: %s"
      ::=  { systemTraps 4 }

systemModel OBJECT-TYPE
    SYNTAX OCTET STRING
    MAX-ACCESS read-only
    STATUS     current
    DESCRIPTION
            "System model name"
    ::= { system 3 }

hostname OBJECT-TYPE
    SYNTAX OCTET STRING
    MAX-ACCESS read-only
    STATUS     current
    DESCRIPTION
            "Host name"
    ::= { system 4 }

serialNumber OBJECT-TYPE
    SYNTAX  OCTET STRING  (SIZE (0..255))
    MAX-ACCESS  read-only
    STATUS  current
    DESCRIPTION
            "Enclosure Serial Number."
    ::= { system 5 }

firmwareVersion OBJECT-TYPE
    SYNTAX OCTET STRING
    MAX-ACCESS read-only
    STATUS     current
    DESCRIPTION
            "Firmware Version"
    ::= { system 6 }

firmwareUpgradeAvailable OBJECT-TYPE
    SYNTAX  Integer32
    MAX-ACCESS  read-only
    STATUS  current
    DESCRIPTION
            "Firmware can upgrade or not"
    ::= { system 7 }

sysFanNumber OBJECT-TYPE
    SYNTAX  Integer32
    MAX-ACCESS  read-only
    STATUS  current
    DESCRIPTION
            "The number of system fan (regardless of
            their current state) present on this system."
    ::= { system 8 }

systemFanTable OBJECT-TYPE
    SYNTAX  SEQUENCE OF SysFanEntryDef
    MAX-ACCESS  not-accessible
    STATUS  current
    DESCRIPTION
            "A list of interface entries.  The number of
            entries is given by the value of SysFanNumber."
    ::= { system 9 }

systemFanEntry OBJECT-TYPE
    SYNTAX  SysFanEntryDef
    MAX-ACCESS  not-accessible
    STATUS  current
    DESCRIPTION
            "An system fan entry containing objects at the
            subnetwork layer and below for a particular
            interface."
    INDEX   { sysFanIndex }
    ::= { systemFanTable 1 }

SysFanEntryDef ::=
    SEQUENCE {
        sysFanIndex
            Integer32 ,
        sysFanDescr
            OCTET STRING,
        sysFanSpeed
            Integer32
    }

sysFanIndex OBJECT-TYPE
    SYNTAX  Integer32 (0..512)
    MAX-ACCESS  not-accessible
    STATUS  current
    DESCRIPTION
            "A unique value for each system fan. Its value
            ranges between 1 and the value of SysFanNumber.  The
            value for each interface must remain constant at
            least from one re-initialization of the entity's
            network management system to the next re-
            initialization."
    ::= { systemFanEntry 1 }

sysFanDescr OBJECT-TYPE
    SYNTAX  OCTET STRING (SIZE (0..255))
    MAX-ACCESS  read-only
    STATUS  current
    DESCRIPTION
            "A textual string containing information about the
            interface.  This string should include the name of
            the manufacturer, the product name and the version
            of the hardware interface."
    ::= { systemFanEntry 2 }

sysFanSpeed OBJECT-TYPE
    SYNTAX  Integer32
    MAX-ACCESS  read-only
    STATUS  current
    DESCRIPTION
            "System fan speed."
    ::= { systemFanEntry 3 }

cpuTemperature OBJECT-TYPE
    SYNTAX Integer32
    MAX-ACCESS read-only
    STATUS     current
    DESCRIPTION
        "CPU temperature"
    ::= { system 10 }

systemTemperature OBJECT-TYPE
    SYNTAX Integer32
    MAX-ACCESS read-only
    STATUS     current
    DESCRIPTION
        "System temperature"
    ::= { system 11 }

systemCPU-Usage OBJECT-TYPE
    SYNTAX Integer32
    MAX-ACCESS read-only
    STATUS     current
    DESCRIPTION
        "System CPU usage"
    ::= { system 12 }

systemTotalMem OBJECT-TYPE
    SYNTAX Counter64
    MAX-ACCESS read-only
    STATUS     current
    DESCRIPTION
        "System total memory"
    ::= { system 13}

systemFreeMem OBJECT-TYPE
    SYNTAX Counter64
    MAX-ACCESS read-only
    STATUS     current
    DESCRIPTION
        "System free memory"
    ::= { system 14 }

systemAvailableMem OBJECT-TYPE
    SYNTAX Counter64
    MAX-ACCESS read-only
    STATUS     current
    DESCRIPTION
        "System available memory"
    ::= { system 15 }

systemUsedMemory OBJECT-TYPE
    SYNTAX Counter64
    MAX-ACCESS read-only
    STATUS     current
    DESCRIPTION
        "System used memory"
    ::= { system 16 }

systemCacheMemory OBJECT-TYPE
    SYNTAX Counter64
    MAX-ACCESS read-only
    STATUS     current
    DESCRIPTION
        "System cached memory"
    ::= { system 17 }

systemBufferMemory OBJECT-TYPE
    SYNTAX Counter64
    MAX-ACCESS read-only
    STATUS     current
    DESCRIPTION
        "System buffered memory"
    ::= { system 18 }

sysPowerStatus OBJECT-TYPE
    SYNTAX  INTEGER {
                   failed(-1),
                   ok(0)
                   }
    MAX-ACCESS  read-only
    STATUS  current
    DESCRIPTION
         "System power status."
    ::= { system 19 }

sysUPSStatus OBJECT-TYPE
    SYNTAX  Integer32
    MAX-ACCESS  read-only
    STATUS  current
    DESCRIPTION
         "System UPS status."
    ::= { system 20 }

sysUptime OBJECT-TYPE
    SYNTAX     TimeTicks
    MAX-ACCESS read-only
    STATUS     current
    DESCRIPTION
        "The amount of time since this host was last
        initialized.  Note that this is different from
        sysUpTime in the SNMPv2-MIB [RFC1907] because
        sysUpTime is the uptime of the network management
        portion of the system."
    ::= { system 21 }

 -- external
    external            OBJECT IDENTIFIER ::= { qutshero 13 }

upsStatus OBJECT-TYPE
    SYNTAX OCTET STRING
    MAX-ACCESS read-only
    STATUS     current
    DESCRIPTION
            "ups status"
    ::= { external 1 }

upsModel OBJECT-TYPE
    SYNTAX OCTET STRING
    MAX-ACCESS read-only
    STATUS     current
    DESCRIPTION
            "ups model name"
    ::= { external 2 }

upsDeviceManufacturer OBJECT-TYPE
    SYNTAX OCTET STRING
    MAX-ACCESS read-only
    STATUS     current
    DESCRIPTION
            "ups manufacturer name"
    ::= { external 3 }

upsDeviceSerial OBJECT-TYPE
    SYNTAX OCTET STRING
    MAX-ACCESS read-only
    STATUS     current
    DESCRIPTION
            "ups serial number"
    ::= { external 4 }

upsManufacturerDate OBJECT-TYPE
    SYNTAX OCTET STRING
    MAX-ACCESS read-only
    STATUS     current
    DESCRIPTION
            "ups manufacturer date"
    ::= { external 5 }

upsLoadPercentage OBJECT-TYPE
    SYNTAX OCTET STRING
    MAX-ACCESS read-only
    STATUS     current
    DESCRIPTION
            "ups manufacturer date"
    ::= { external 6 }

upsBatteryCharge OBJECT-TYPE
    SYNTAX OCTET STRING
    MAX-ACCESS read-only
    STATUS     current
    DESCRIPTION
            "ups battery charge"
    ::= { external 7 }

upsBatteryChargeWarningLevel OBJECT-TYPE
    SYNTAX OCTET STRING
    MAX-ACCESS read-only
    STATUS     current
    DESCRIPTION
            "ups battery charge warning level"
    ::= { external 8 }

upsBatteryType OBJECT-TYPE
    SYNTAX OCTET STRING
    MAX-ACCESS read-only
    STATUS     current
    DESCRIPTION
            "ups battery type"
    ::= { external 9 }

usbPrinterTable OBJECT-TYPE
    SYNTAX  SEQUENCE OF UsbPrinterTableEntryDef
    MAX-ACCESS  not-accessible
    STATUS  current
    DESCRIPTION
            "A list of printer entries."
    ::= { external 10 }

usbPrinterTableEntry OBJECT-TYPE
    SYNTAX  UsbPrinterTableEntryDef
    MAX-ACCESS  not-accessible
    STATUS  current
    DESCRIPTION
            "An system fan entry containing objects at the
            subnetwork layer and below for a particular
            interface."
    INDEX   { usbPrinterIndex }
    ::= { usbPrinterTable 1 }

UsbPrinterTableEntryDef ::=
    SEQUENCE {
        usbPrinterIndex
            Integer32 ,
        usbPrinterName
            OCTET STRING,
        usbPrinterManufacturer
            OCTET STRING,
        usbPrinterModel
            OCTET STRING,
        usbPrinterStatus
            INTEGER ,
        usbPrinterBonjourPrinterSupportEnabled
            INTEGER ,
        usbPrinterSharingEnabled
            INTEGER
    }

usbPrinterIndex OBJECT-TYPE
    SYNTAX  Integer32 (0..512)
    MAX-ACCESS  not-accessible
    STATUS  current
    DESCRIPTION
            "A unique value for each usb printer."
    ::= { usbPrinterTableEntry 1 }

usbPrinterName OBJECT-TYPE
    SYNTAX  OCTET STRING
    MAX-ACCESS  read-only
    STATUS  current
    DESCRIPTION
            "printer name."
    ::= { usbPrinterTableEntry 2 }

usbPrinterManufacturer OBJECT-TYPE
    SYNTAX  OCTET STRING
    MAX-ACCESS  read-only
    STATUS  current
    DESCRIPTION
            "printer name."
    ::= { usbPrinterTableEntry 3 }

usbPrinterModel OBJECT-TYPE
    SYNTAX  OCTET STRING
    MAX-ACCESS  read-only
    STATUS  current
    DESCRIPTION
            "printer model."
    ::= { usbPrinterTableEntry 4 }

usbPrinterStatus OBJECT-TYPE
    SYNTAX  INTEGER {
                   notDetected(0),
                   detected(1),
                   unknown(2)
                   }
    MAX-ACCESS  read-only
    STATUS  current
    DESCRIPTION
            "printer status."
    ::= { usbPrinterTableEntry 5 }

usbPrinterBonjourPrinterSupportEnabled OBJECT-TYPE
    SYNTAX  INTEGER {
                   no(0),
                   yes(1)
                   }
    MAX-ACCESS  read-only
    STATUS  current
    DESCRIPTION
            "flag of bonjour printer support."
    ::= { usbPrinterTableEntry 6 }

usbPrinterSharingEnabled OBJECT-TYPE
    SYNTAX  INTEGER {
                   no(0),
                   yes(1)
                   }
    MAX-ACCESS  read-only
    STATUS  current
    DESCRIPTION
            "flag of printer sharing."
    ::= { usbPrinterTableEntry 7 }

 -- services
    services            OBJECT IDENTIFIER ::= { qutshero 14 }

nfsV2V3IsEnabled OBJECT-TYPE
    SYNTAX  INTEGER {
                   no(0),
                   yes(1)
                   }
    MAX-ACCESS  read-only
    STATUS  current
    DESCRIPTION
         "NFS V2/V3 enable flag"
    ::= { services 1 }

nfsV4IsEnabled OBJECT-TYPE
    SYNTAX  INTEGER {
                   no(0),
                   yes(1)
                   }
    MAX-ACCESS  read-only
    STATUS  current
    DESCRIPTION
         "NFS V4 enable flag"
    ::= { services 2 }

httpPort OBJECT-TYPE
    SYNTAX  Integer32
    MAX-ACCESS  read-only
    STATUS  current
    DESCRIPTION
         "HTTP port"
    ::= { services 3 }

httpsPort OBJECT-TYPE
    SYNTAX  Integer32
    MAX-ACCESS  read-only
    STATUS  current
    DESCRIPTION
         "HTTPs port"
    ::= { services 4 }

sshIsEnabled OBJECT-TYPE
    SYNTAX  INTEGER {
                   no(0),
                   yes(1)
                   }
    MAX-ACCESS  read-only
    STATUS  current
    DESCRIPTION
         "SSH enable flag"
    ::= { services 5 }

sshSFTPEnabled OBJECT-TYPE
    SYNTAX  INTEGER {
                   no(0),
                   yes(1)
                   }
    MAX-ACCESS  read-only
    STATUS  current
    DESCRIPTION
         "SFTP enable flag"
    ::= { services 6 }

sshPortNumber OBJECT-TYPE
    SYNTAX  Integer32
    MAX-ACCESS  read-only
    STATUS  current
    DESCRIPTION
         "SSH port number"
    ::= { services 7 }

telnetIsEnabled OBJECT-TYPE
    SYNTAX  INTEGER {
                   no(0),
                   yes(1)
                   }
    MAX-ACCESS  read-only
    STATUS  current
    DESCRIPTION
         "Telnet enable flag"
    ::= { services 8 }

telnetPortNumber OBJECT-TYPE
    SYNTAX  Integer32
    MAX-ACCESS  read-only
    STATUS  current
    DESCRIPTION
         "Telnet port number"
    ::= { services 9 }

ftpEnabled OBJECT-TYPE
    SYNTAX  INTEGER {
                   no(0),
                   yes(1)
                   }
    MAX-ACCESS  read-only
    STATUS  current
    DESCRIPTION
         "FTP enable flag"
    ::= { services 10 }

ftpProtocolStandardEnabled OBJECT-TYPE
    SYNTAX  INTEGER {
                   no(0),
                   yes(1)
                   }
    MAX-ACCESS  read-only
    STATUS  current
    DESCRIPTION
         "FTP standard protocol flag"
    ::= { services 11 }

ftpProtocolSSL-TLSEnabled OBJECT-TYPE
    SYNTAX  INTEGER {
                   no(0),
                   yes(1)
                   }
    MAX-ACCESS  read-only
    STATUS  current
    DESCRIPTION
         "FTP SSL/TLS protocol flag"
    ::= { services 12 }

ftpPortNumber OBJECT-TYPE
    SYNTAX  Integer32
    MAX-ACCESS  read-only
    STATUS  current
    DESCRIPTION
         "FTP port number"
    ::= { services 13 }

ftpUnicodeSupportEnabled OBJECT-TYPE
    SYNTAX  INTEGER {
                   no(0),
                   yes(1)
                   }
    MAX-ACCESS  read-only
    STATUS  current
    DESCRIPTION
         "FTP support unicode flag"
    ::= { services 14 }

ftpAnnonymousaccessEnabled OBJECT-TYPE
    SYNTAX  INTEGER {
                   no(0),
                   yes(1)
                   }
    MAX-ACCESS  read-only
    STATUS  current
    DESCRIPTION
         "FTP annonymous access flag"
    ::= { services 15 }

ftpMaxConnectionsAllowed OBJECT-TYPE
    SYNTAX  Integer32
    MAX-ACCESS  read-only
    STATUS  current
    DESCRIPTION
         "FTP max connections"
    ::= { services 16 }

ftpMaxConnectionsPerAccount OBJECT-TYPE
    SYNTAX  Integer32
    MAX-ACCESS  read-only
    STATUS  current
    DESCRIPTION
         "FTP max connections per account"
    ::= { services 17 }

ftpMaxUploadRate OBJECT-TYPE
    SYNTAX  INTEGER {
                   unlimited(0)
                   }
    MAX-ACCESS  read-only
    STATUS  current
    DESCRIPTION
         "FTP max upload rate (KB/s)"
    ::= { services 18 }

ftpMaxDownloadRate OBJECT-TYPE
    SYNTAX  INTEGER  {
                   unlimited(0)
                   }
    MAX-ACCESS  read-only
    STATUS  current
    DESCRIPTION
         "FTP max download rate (KB/s)"
    ::= { services 19 }

 -- applications
    applications            OBJECT IDENTIFIER ::= { qutshero 15 }

applicationsTable OBJECT-TYPE
    SYNTAX  SEQUENCE OF ApplicationsTableEntryDef
    MAX-ACCESS  not-accessible
    STATUS  current
    DESCRIPTION
            "A list of application entries."
    ::= { applications 1 }

applicationsTableEntry OBJECT-TYPE
    SYNTAX  ApplicationsTableEntryDef
    MAX-ACCESS  not-accessible
    STATUS  current
    DESCRIPTION
            "An application entry containing the
            meta of an application include app
            name, version..."
    INDEX   { appIndex }
    ::= { applicationsTable 1 }

ApplicationsTableEntryDef ::=
    SEQUENCE {
        appIndex
            Integer32 ,
        appName
            OCTET STRING,
        appVersion
            OCTET STRING,
        appInstallationDate
            OCTET STRING,
        appLatestVersion
            OCTET STRING,
        appDisplayPermission
            Integer32
    }

appIndex OBJECT-TYPE
    SYNTAX  Integer32 (0..512)
    MAX-ACCESS  not-accessible
    STATUS  current
    DESCRIPTION
            "A unique value for each application."
    ::= { applicationsTableEntry 1 }

appName OBJECT-TYPE
    SYNTAX  OCTET STRING
    MAX-ACCESS  read-only
    STATUS  current
    DESCRIPTION
            "application name."
    ::= { applicationsTableEntry 2 }

appVersion OBJECT-TYPE
    SYNTAX  OCTET STRING
    MAX-ACCESS  read-only
    STATUS  current
    DESCRIPTION
            "application version."
    ::= { applicationsTableEntry 3 }

appInstallationDate OBJECT-TYPE
    SYNTAX  OCTET STRING
    MAX-ACCESS  read-only
    STATUS  current
    DESCRIPTION
            "application installation date."
    ::= { applicationsTableEntry 4 }

appLatestVersion OBJECT-TYPE
    SYNTAX  OCTET STRING
    MAX-ACCESS  read-only
    STATUS  current
    DESCRIPTION
            "application lated version."
    ::= { applicationsTableEntry 5 }

appDisplayPermission OBJECT-TYPE
    SYNTAX  INTEGER {
                   adminOnly(0),
                   adminGroup(1),
                   everyUser(2)
                   }
    MAX-ACCESS  read-only
    STATUS  current
    DESCRIPTION
            "application can browse by whom."
    ::= { applicationsTableEntry 6 }

END
